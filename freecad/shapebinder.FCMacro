body = App.activeDocument().addObject('PartDesign::Body','foot_plate')
for o in [ 
	"FrameFLVSlot",
]:
	if 1:
		sb = body.newObject('PartDesign::ShapeBinder',o + '_bind')
		ob = App.getDocument('frame').getObject(o)
		sb.TraceSupport = True
		sb.Support = [ob, '']
	else:
		sb = App.ActiveDocument.getObject(o + '_bind')
		ob = App.getDocument('frame').getObject(o)
		sb.Support = [(ob, '')]

App.ActiveDocument.recompute()
